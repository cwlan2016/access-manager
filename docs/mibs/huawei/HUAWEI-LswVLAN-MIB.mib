-- ==================================================================
-- Copyright (C) 2002 by  HUAWEI TECHNOLOGIES. All rights reserved.
--
-- Description: HUAWEI Lan Switch VLAN MIB
-- Reference:
-- Version: V1.7
-- History:
--(1) Created by Zhangshilin, 2001.06.29
--(2) Revised by Qi Zhenglin, 2002.01.08
--   V1.1 2004-09-08 modify STATUS of hwLswVlanProtoObject from mandatory to current by gaolong.
--   V1.2 2004-09-23 add ifEntry IMPORT clause by gaolong
--   V1.3 2004-10-12 updated by gaolong
--        Import TEXTUAL-CONVENTION and OBJECT-IDENTITY.
--        Relocate hwLswVlan MODULE-IDENTITY.
--        Change MAX-ACCESS clause value of hwVLANMibSwitchGarpStatClear to read-write.
--   V1.4 2004-12-28 modified by jiaoyi
--          Add hwdot1qVlanMulticast in hwdot1qVlanMIBTable
--        2005-01-22 update by wangyingxia
--          Add all objects of hwLswVlanMngObject from HUAWEI-LswINF-MIB into this MIB
--          Add TruthValue, RowStatus, TimeTicks, IpAddress, SnmpAdminString, VlanIndex, PortList
--          Remove InterfaceIndex and import it from HUAWEI-LswINF-MIB
--   V1.5 2005-01-22
--        Add superVlan to hwdot1qVlanType by sunqiang
--   V1.6 2005-05-18
--        Add hwdot1qVlanBatchMIBTable by lipei
--   V1.7 2005-08-08
--        Add HwVlanIndex and modified all VlanIndex to HwVlanIndex by longyin
-- ==================================================================
-- ==================================================================
--
-- Varibles and types be imported
--
-- ==================================================================
HUAWEI-LswVLAN-MIB DEFINITIONS ::= BEGIN
IMPORTS

    DisplayString, TimeInterval, TEXTUAL-CONVENTION, TruthValue, RowStatus
        FROM SNMPv2-TC

    Counter32, Integer32,  TimeTicks, IpAddress
        FROM SNMPv2-SMI

    SnmpAdminString
        FROM SNMP-FRAMEWORK-MIB

    lswCommon
        FROM HUAWEI-3COM-OID-MIB

    ifEntry, ifIndex
        FROM RFC1213-MIB

    hwifVLANTrunkStatusEntry, hwifVLANTrunkIndex, VlanIndex, PortList,InterfaceIndex
        FROM HUAWEI-LswINF-MIB;

    hwLswVlan OBJECT IDENTIFIER ::= { lswCommon 2 }

    HwVlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Integer32(0..2147483647)
    
-- ==================================================================
--
-- ======================= definition begin =========================
--
-- ==================================================================

    hwLswVlanMngObject OBJECT-IDENTITY
            STATUS current
            DESCRIPTION
                "Description."
            ::= { hwLswVlan 1 }

    hwdot1qVlanMIBTable OBJECT-TYPE
        SYNTAX SEQUENCE OF HwDot1qVlanMIBEntry
        MAX-ACCESS not-accessible
        STATUS current
        DESCRIPTION " VLAN MIB table  "
        ::= { hwLswVlanMngObject  1 }


    hwdot1qVlanMIBEntry OBJECT-TYPE
        SYNTAX HwDot1qVlanMIBEntry
        MAX-ACCESS not-accessible
        STATUS current
        DESCRIPTION "  Entries of VLAN MIB table "
        INDEX   { hwdot1qVlanIndex }
        ::= { hwdot1qVlanMIBTable 1}

    HwDot1qVlanMIBEntry ::=
    SEQUENCE {
        hwdot1qVlanIndex    HwVlanIndex   ,
        hwdot1qVlanName     SnmpAdminString     ,
        hwdot1qVlanPorts    PortList    ,
        hwdot1qVlanType     INTEGER ,
        hwdot1qVlanMacFilter    TruthValue  ,
        hwdot1qVlanMcastUnknownProtos   TruthValue  ,
        hwExistInterface    TruthValue  ,
        hwVlanInterfaceIndex    INTEGER ,
        hwdot1qVlanMacLearn TruthValue  ,
        hwdot1qVlanStatus   INTEGER     ,
        hwdot1qVlanCreationTime TimeTicks   ,
        hwdot1qVlanPriority INTEGER ,
        hwdot1qVlanRowStatus    RowStatus,
        hwdot1qVlanBroadcastSuppression INTEGER,
        hwdot1qVlanBcastSuppressionPPS   INTEGER,
        hwdot1qVlanMulticast INTEGER
        }



    hwdot1qVlanIndex OBJECT-TYPE
        SYNTAX  HwVlanIndex
        MAX-ACCESS read-only
        STATUS current
        DESCRIPTION " The VLAN-ID "
        ::= { hwdot1qVlanMIBEntry 1 }


    hwdot1qVlanName  OBJECT-TYPE
        SYNTAX  SnmpAdminString (SIZE (0..32))
        MAX-ACCESS read-write
        STATUS current
        DESCRIPTION " Name of the VLAN "
        ::= { hwdot1qVlanMIBEntry 2 }


    hwdot1qVlanPorts OBJECT-TYPE
        SYNTAX  PortList
        MAX-ACCESS read-write
        STATUS current
        DESCRIPTION " Port list of the VLAN "
        ::= { hwdot1qVlanMIBEntry 3 }


    hwdot1qVlanType  OBJECT-TYPE
        SYNTAX  INTEGER
        {
        superVlan   (1),
        common-vlan (2),
        sub-vlan    (3),
        isolate-user-vlan(4),
        secondary-vlan(5)
        }
        MAX-ACCESS read-write
        STATUS current
        DESCRIPTION " vlan types:SuperVlan(1), Common vlan(2), and Sub-vlan(3)  "
        ::= { hwdot1qVlanMIBEntry 4 }


    hwdot1qVlanMacFilter OBJECT-TYPE
        SYNTAX  TruthValue
        MAX-ACCESS read-only
        STATUS current
        DESCRIPTION " Whether to filter MAC addresses "
        ::= { hwdot1qVlanMIBEntry 5 }


    hwdot1qVlanMcastUnknownProtos OBJECT-TYPE
        SYNTAX  TruthValue
        MAX-ACCESS read-only
        STATUS current
        DESCRIPTION " Whether to broadcast the unknown packets "
        ::= { hwdot1qVlanMIBEntry 6 }


    hwExistInterface OBJECT-TYPE
        SYNTAX  TruthValue
        MAX-ACCESS read-only
        STATUS current
        DESCRIPTION " Whether there is virtual interface "
        ::= { hwdot1qVlanMIBEntry 7 }


    hwVlanInterfaceIndex OBJECT-TYPE
        SYNTAX  INTEGER
        MAX-ACCESS read-only
        STATUS current
        DESCRIPTION " Whether vlan interface is configured on vlan. If vlan interface is configured,
        the value of the node is vlan id, else the value is 0. "
        ::= { hwdot1qVlanMIBEntry 8 }


    hwdot1qVlanMacLearn OBJECT-TYPE
        SYNTAX  TruthValue
        MAX-ACCESS read-only
        STATUS current
        DESCRIPTION " MAC address learning identity (common vlan/Sub-vlan) "
        ::= { hwdot1qVlanMIBEntry 9 }


    hwdot1qVlanStatus OBJECT-TYPE
        SYNTAX  INTEGER
        {
        other       (1),
        static   (2),
        dynamic (3)
        }
        MAX-ACCESS read-only
        STATUS current
        DESCRIPTION " Status of the VLAN  "
        ::= { hwdot1qVlanMIBEntry 10 }


    hwdot1qVlanCreationTime OBJECT-TYPE
        SYNTAX  TimeTicks
        MAX-ACCESS read-only
        STATUS current
        DESCRIPTION " sysUPTime when the VLAN is created "
        ::= { hwdot1qVlanMIBEntry 11 }


    hwdot1qVlanPriority OBJECT-TYPE
        SYNTAX  INTEGER (0..7)
        MAX-ACCESS read-write
        STATUS current
        DESCRIPTION " Priority of the VLAN "
        DEFVAL  {0}
        ::= { hwdot1qVlanMIBEntry 12 }


    hwdot1qVlanRowStatus  OBJECT-TYPE
        SYNTAX  RowStatus
        MAX-ACCESS read-create
        STATUS current
        DESCRIPTION " Operation status "
        ::= { hwdot1qVlanMIBEntry 13 }

    hwdot1qVlanBroadcastSuppression  OBJECT-TYPE
        SYNTAX  INTEGER (0..100)
        MAX-ACCESS read-write
        STATUS current
        DESCRIPTION " If broadcast can be controlled in this vlan and the control ratio. The vlaue of 100 indicates no control is exerted.
            If the device doesn't support broadcast control by vlan, then set operation of this node will be responsed with fault, but
            with 100 for read operation.The default value is 100, i.e no broadcast control. But to device which doesn't support, this value
            has no actual meaning. "
        DEFVAL { 100 }
        ::= { hwdot1qVlanMIBEntry 14 }

    hwdot1qVlanBcastSuppressionPPS   OBJECT-TYPE
        SYNTAX  INTEGER (0..148800)
        MAX-ACCESS read-write
        STATUS current
        DESCRIPTION " If the broadcast can be controlled with pps(packet per second)type, The value of 0 indicates no control is
            exerted. This mode conflictes with hwdot1qVlanBroadcastSuppression. If the mode is set, hwdot1qVlanBroadcastSuppression
            is unavailable. And vice versa."
        ::= { hwdot1qVlanMIBEntry 15 }

    hwdot1qVlanMulticast  OBJECT-TYPE
        SYNTAX  INTEGER
        {
        disable  (0),
        enable   (1)
        }
        MAX-ACCESS read-write
        STATUS current
        DESCRIPTION "Multicast vlan. The default value is disable(0)."
        ::= { hwdot1qVlanMIBEntry 16 }

    hwVlanInterfaceTable OBJECT-TYPE
        SYNTAX SEQUENCE OF HwVlanInterfaceEntry
        MAX-ACCESS not-accessible
        STATUS current
        DESCRIPTION " Virtual interface configuration table  "
        ::= { hwLswVlanMngObject  2}


    hwVlanInterfaceEntry OBJECT-TYPE
        SYNTAX HwVlanInterfaceEntry
        MAX-ACCESS not-accessible
        STATUS current
        DESCRIPTION " Entries of virtual interface configuration table  "
        INDEX   { hwVlanInterfaceID }
        ::= {hwVlanInterfaceTable 1}

    HwVlanInterfaceEntry    ::=
    SEQUENCE {
        hwVlanInterfaceID       INTEGER ,
        hwdot1qVlanID       HwVlanIndex   ,
        hwdot1qVlanIpAddress        IpAddress   ,
        hwdot1qVlanIpAddressMask    IpAddress   ,
        hwVlanInterfaceAdminStatus  INTEGER ,
        hwVlanInterfaceFrameType    INTEGER ,
        hwInterfaceRowStatus        RowStatus,
        hwVlanInterfaceIpMethod     INTEGER
        }

    hwVlanInterfaceID OBJECT-TYPE
        SYNTAX  INTEGER
        MAX-ACCESS read-only
        STATUS current
        DESCRIPTION " Index of VLAN virtual interfaces "
        ::= { hwVlanInterfaceEntry 1 }


    hwdot1qVlanID OBJECT-TYPE
        SYNTAX  HwVlanIndex
        MAX-ACCESS read-only
        STATUS current
        DESCRIPTION " VLANID "
        ::= { hwVlanInterfaceEntry 2 }


    hwdot1qVlanIpAddress OBJECT-TYPE
        SYNTAX  IpAddress
        MAX-ACCESS read-write
        STATUS current
        DESCRIPTION " IP address of interface "
        ::= { hwVlanInterfaceEntry 3 }


    hwdot1qVlanIpAddressMask OBJECT-TYPE
        SYNTAX  IpAddress
        MAX-ACCESS read-write
        STATUS current
        DESCRIPTION " IP address mask of interface "
        ::= { hwVlanInterfaceEntry 4 }

    hwVlanInterfaceAdminStatus OBJECT-TYPE
        SYNTAX  INTEGER
        {
        up      (1),
        down    (2)
        }
        MAX-ACCESS read-write
        STATUS current
        DESCRIPTION " Status of VLAN virtual interfaces  "
        ::= { hwVlanInterfaceEntry 5 }

    hwVlanInterfaceFrameType OBJECT-TYPE
        SYNTAX  INTEGER
        {
        ethernet-ii     (1) ,
        ethernet-snap   (2) ,
        ethernet-8022   (3) ,
        ethernet-8023   (4)
        }
        MAX-ACCESS read-only
        STATUS current
        DESCRIPTION " Frame type accepted by VLAN virtual interfaces "
        ::= { hwVlanInterfaceEntry 6 }


    hwInterfaceRowStatus OBJECT-TYPE
        SYNTAX  RowStatus
        MAX-ACCESS read-create
        STATUS current
        DESCRIPTION " Operation status "
        ::= { hwVlanInterfaceEntry 7 }


    hwVlanInterfaceIpMethod OBJECT-TYPE
        SYNTAX  INTEGER
        {
        assigned-ip    (1),
        dhcp-ip        (2),
        bootp-ip       (3)
        }
        MAX-ACCESS read-write
        STATUS current
        DESCRIPTION " vlan interface ip address acquiring method which is manual, dhcp or bootp "
        ::= { hwVlanInterfaceEntry 8 }

    hwifIsolateMappingTable OBJECT-TYPE
        SYNTAX SEQUENCE OF HwifIsolateMappingEntry
        MAX-ACCESS not-accessible
        STATUS current
        DESCRIPTION "Secondary vlan lists of Isolate-VLANs"
        ::= { hwLswVlanMngObject  4 }


    hwifIsolateMappingEntry OBJECT-TYPE
        SYNTAX HwifIsolateMappingEntry
        MAX-ACCESS not-accessible
        STATUS current
        DESCRIPTION "Secondary vlan lists of Isolate-VLANs"
        INDEX   { hwifIsolatePrimaryVlanID }
        ::= { hwifIsolateMappingTable 1}

    HwifIsolateMappingEntry   ::=
    SEQUENCE {
        hwifIsolatePrimaryVlanID  HwVlanIndex   ,
        hwifIsolateSecondaryVlanlistLow   OCTET STRING,
        hwifIsolateSecondaryVlanlistHigh OCTET STRING
        }

    hwifIsolatePrimaryVlanID OBJECT-TYPE
        SYNTAX  HwVlanIndex
        MAX-ACCESS read-only
        STATUS current
        DESCRIPTION " Primary VLAN ID "
        ::= { hwifIsolateMappingEntry 1 }


    hwifIsolateSecondaryVlanlistLow OBJECT-TYPE
        SYNTAX  OCTET STRING(SIZE(0..256))
        MAX-ACCESS read-write
        STATUS current
        DESCRIPTION " The lowest possible value of the list of the secondary VLANs to be added to the Isolate-VLAN "
        ::= { hwifIsolateMappingEntry 2 }

    hwifIsolateSecondaryVlanlistHigh OBJECT-TYPE
        SYNTAX  OCTET STRING(SIZE(0..256))
        MAX-ACCESS read-write
        STATUS current
        DESCRIPTION " The highest possible value of the list of the secondary VLANs to be added to the Isolate-VLAN "
        ::= { hwifIsolateMappingEntry 3 }

    hwVlanInterfaceAddrTable OBJECT-TYPE
        SYNTAX SEQUENCE OF HwVlanInterfaceAddrEntry
        MAX-ACCESS not-accessible
        STATUS current
        DESCRIPTION " VLAN interface IP address configuration table "
        ::= { hwLswVlanMngObject 5 }

    hwVlanInterfaceAddrEntry OBJECT-TYPE
        SYNTAX HwVlanInterfaceAddrEntry
        MAX-ACCESS not-accessible
        STATUS current
        DESCRIPTION " Entries of VLAN interface IP address configuration table "
        INDEX   { hwVlanInterfaceIpIfIndex, hwVlanInterfaceIpAddr }
        ::= { hwVlanInterfaceAddrTable 1 }

    HwVlanInterfaceAddrEntry ::=
    SEQUENCE {
        hwVlanInterfaceIpIfIndex     INTEGER,
        hwVlanInterfaceIpAddr        IpAddress,
        hwVlanInterfaceIpMask        IpAddress,
        hwVlanInterfaceIpType        INTEGER,
        hwVlanInterfaceIpRowStatus   RowStatus
        }

    hwVlanInterfaceIpIfIndex OBJECT-TYPE
        SYNTAX  INTEGER
        MAX-ACCESS read-only
        STATUS current
        DESCRIPTION " Index of VLAN interfaces "
        ::= { hwVlanInterfaceAddrEntry 1 }

    hwVlanInterfaceIpAddr OBJECT-TYPE
        SYNTAX  IpAddress
        MAX-ACCESS read-write
        STATUS current
        DESCRIPTION " IP address of VLAN interface. When taking destory operation,
                     you could set it zero to destory all IP addresses(but cluster
                     IP address) in this VLAN interface. "
        ::= { hwVlanInterfaceAddrEntry 2 }

    hwVlanInterfaceIpMask OBJECT-TYPE
        SYNTAX  IpAddress
        MAX-ACCESS read-write
        STATUS current
        DESCRIPTION " IP address mask of VLAN interface. When destory single IP address,
                     you must set it correct to relative IP address "
        ::= { hwVlanInterfaceAddrEntry 3 }

    hwVlanInterfaceIpType OBJECT-TYPE
        SYNTAX  INTEGER
        {
        primary     (1),
        sub         (2),
        cluster     (3)
        }
        MAX-ACCESS read-write
        STATUS current
        DESCRIPTION " IP address type. cluster(3) will only be set when taking GET or
                     GET NEXT operation. primary(1) is optional when taking SET primary
                     IP address operation "
        ::= { hwVlanInterfaceAddrEntry 4 }

    hwVlanInterfaceIpRowStatus OBJECT-TYPE
        SYNTAX  RowStatus
        MAX-ACCESS read-create
        STATUS current
        DESCRIPTION " Operation status. active(1) will only be set when taking GET or
                     GET NEXT operation. createAndGo(4) and destory(6) is valid when
                     taking SET operation "
        ::= { hwVlanInterfaceAddrEntry 5 }


    hwdot1qVlanBatchMIBTable  OBJECT-TYPE
        SYNTAX SEQUENCE OF HwDot1qVlanBatchMIBEntry
        MAX-ACCESS not-accessible
        STATUS current
        DESCRIPTION
            " VLAN batch creation configuration table. "
        ::= { hwLswVlanMngObject  6 }

    hwDot1qVlanBatchMIBEntry OBJECT-TYPE
        SYNTAX HwDot1qVlanBatchMIBEntry
        MAX-ACCESS not-accessible
        STATUS current
        DESCRIPTION
            " VLAN batch creation configuration entry. "
        INDEX   { hwdot1qVlanBatchOperIndex }
        ::= { hwdot1qVlanBatchMIBTable 1}

    HwDot1qVlanBatchMIBEntry::=
        SEQUENCE {
            hwdot1qVlanBatchOperIndex
                Integer32,
            hwdot1qVlanBatchStartIndex
                HwVlanIndex,
            hwdot1qVlanBatchEndIndex
                HwVlanIndex,
            hwdot1qVlanBatchOperStatus
                INTEGER,
            hwdot1qVlanBatchRowStatus
                RowStatus
        }

    hwdot1qVlanBatchOperIndex OBJECT-TYPE
        SYNTAX  Integer32
        MAX-ACCESS read-only
        STATUS current
        DESCRIPTION
            " The consequence of operation. "
        ::= { hwDot1qVlanBatchMIBEntry 1 }

    hwdot1qVlanBatchStartIndex OBJECT-TYPE
        SYNTAX  HwVlanIndex
        MAX-ACCESS read-write
        STATUS current
        DESCRIPTION
            " The value of start VLAN-ID. "
        ::= { hwDot1qVlanBatchMIBEntry 2 }

    hwdot1qVlanBatchEndIndex OBJECT-TYPE
        SYNTAX  HwVlanIndex
        MAX-ACCESS read-write
        STATUS current
        DESCRIPTION
            " The value of end VLAN-ID. "
        ::= { hwDot1qVlanBatchMIBEntry 3 }

    hwdot1qVlanBatchOperStatus OBJECT-TYPE
        SYNTAX  INTEGER
        {
            opInprogress      (1), -- If the operation is running, the system
                                   -- will return OpInprogress.
            opfailure         (2), -- If the operation is failure, the system
                                   -- will return Opfailure.
            opsuccess         (3), -- If the operation is success, the system
                                   -- will return Opsuccess.
            opsuccesspartial  (4)  -- If the operation is success partially,
                                   -- the system will return Opsuccesspartial.
        }
        MAX-ACCESS read-only
        STATUS current
        DESCRIPTION
            " The status of operation. "
        ::= { hwDot1qVlanBatchMIBEntry 4 }

    hwdot1qVlanBatchRowStatus OBJECT-TYPE
        SYNTAX  RowStatus
        MAX-ACCESS read-create
        STATUS current
        DESCRIPTION
            " The row status of HwDot1qVlanBatchMIBEntry. "
        ::= { hwDot1qVlanBatchMIBEntry 5 }


    hwLswVlanProtoObject OBJECT-IDENTITY
            STATUS current
            DESCRIPTION
                "Description."
            ::= { hwLswVlan 2 }

     hwVLANMibGarpLeaveAllTime OBJECT-TYPE
        SYNTAX      TimeInterval
        MAX-ACCESS  read-write
        STATUS      current
        DESCRIPTION
            "The GARP LeaveAll time, in centiseconds."
        DEFVAL      { 1000 }
        ::= { hwLswVlanProtoObject 14 }

     hwvLANMibSwitchCountTable OBJECT-TYPE
        SYNTAX  SEQUENCE OF HwVLANMibSwitchCountEntry
        MAX-ACCESS not-accessible
        STATUS   current
        DESCRIPTION "A table containing the information various statistics of switch  "
        ::= {hwLswVlanProtoObject 15 }


     hwvLANMibSwitchCountEntry OBJECT-TYPE
        SYNTAX  HwVLANMibSwitchCountEntry
        MAX-ACCESS not-accessible
        STATUS current
        DESCRIPTION "A table containing the information various statistics of switch  "
        AUGMENTS    {hwifVLANTrunkStatusEntry  }
        ::= {hwvLANMibSwitchCountTable 1}

    HwVLANMibSwitchCountEntry   ::=
    SEQUENCE {
        hwVLANMibSwitchGMRPRXPkt    Counter32,
        hwVLANMibSwitchGVRPRXPkt    Counter32   ,
        hwVLANMibSwitchGMRPTXPkt    Counter32   ,
        hwVLANMibSwitchGVRPTXPkt    Counter32   ,
        hwVLANMibSwitchDiscardedPkt Counter32  ,
        hwVLANMibSwitchGarpStatClear INTEGER
        }



     hwVLANMibSwitchGMRPRXPkt OBJECT-TYPE
        SYNTAX  Counter32
        MAX-ACCESS read-only
        STATUS current
        DESCRIPTION " 1. Number of GMRP frames received "
        ::= { hwvLANMibSwitchCountEntry 1 }


     hwVLANMibSwitchGVRPRXPkt OBJECT-TYPE
        SYNTAX  Counter32
        MAX-ACCESS read-only
        STATUS current
        DESCRIPTION " 2. Number of GVRP frames received "
        ::= { hwvLANMibSwitchCountEntry 2 }


     hwVLANMibSwitchGMRPTXPkt OBJECT-TYPE
        SYNTAX  Counter32
        MAX-ACCESS read-only
        STATUS current
        DESCRIPTION " 3. Number of GMRP frames transmitted "
        ::= { hwvLANMibSwitchCountEntry 3 }


     hwVLANMibSwitchGVRPTXPkt  OBJECT-TYPE
         SYNTAX  Counter32
         MAX-ACCESS read-only
         STATUS current
         DESCRIPTION " 4. Number of GVRP frames transmitted "
         ::= { hwvLANMibSwitchCountEntry 4 }

     hwVLANMibSwitchDiscardedPkt  OBJECT-TYPE
         SYNTAX  Counter32
         MAX-ACCESS read-only
         STATUS current
         DESCRIPTION " Number of discarded frames  "
         ::= { hwvLANMibSwitchCountEntry 5 }


     hwVLANMibSwitchGarpStatClear OBJECT-TYPE
        SYNTAX  INTEGER {clear(1)}
        MAX-ACCESS read-write
        STATUS current
        DESCRIPTION " Clear various Statistics viz. read operation not supported."
        ::= { hwvLANMibSwitchCountEntry 6 }


     hwvLANMibHoldTimeTable OBJECT-TYPE
        SYNTAX  SEQUENCE OF HwVLANMibHoldTimeEntry
        MAX-ACCESS not-accessible
        STATUS   current
        DESCRIPTION "   A table for setting/getting the Hold Time for a particular port     "
        ::= {hwLswVlanProtoObject 16 }


     hwvLANMibHoldTimeEntry OBJECT-TYPE
        SYNTAX HwVLANMibHoldTimeEntry
        MAX-ACCESS not-accessible
        STATUS   current
        DESCRIPTION "   A table for setting/getting the Hold Time for a particular port     "
         AUGMENTS    { ifEntry }
        ::= {hwvLANMibHoldTimeTable 1 }


    HwVLANMibHoldTimeEntry  ::=
    SEQUENCE {
        hwVLANMibHoldTime   INTEGER
        }


     hwVLANMibHoldTime OBJECT-TYPE
        SYNTAX  INTEGER  (10..32765)
        MAX-ACCESS read-write
        STATUS current
        DESCRIPTION " HoldTime of the port"
        DEFVAL  {10}
        ::= { hwvLANMibHoldTimeEntry 1 }


END
